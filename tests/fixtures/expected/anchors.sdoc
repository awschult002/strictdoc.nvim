[DOCUMENT]
TITLE: Hello world doc

[[SECTION]]
  TITLE: Referencing section

  [TEXT]
  STATEMENT: >>>
See the [LINK: AD1] for more details.

See the [LINK: Software_requirements_specification] for more details.

See the [LINK: Interface_Control_Document] for more details.
  <<<

[[/SECTION]]

[[SECTION]]
  TITLE: Section with anchor

  [TEXT]
  STATEMENT: >>>
Anchors start.

[ANCHOR: AD1]

1) AD1. Software user manual.

[ANCHOR: Software_requirements_specification]

2) AD2. Software requirements specification.

[ANCHOR: Interface_Control_Document, Interface Control Document]

3) AD3. Interface Control Document.

Anchors end.
  <<<

[[/SECTION]]
